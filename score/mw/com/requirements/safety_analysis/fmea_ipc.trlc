/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package Communication

import ScoreReq

ScoreReq.FailureMode SkeletonNotOffered{
    guideword = ScoreReq.GuideWord.LossOfFunction
    description = "Skeleton Not Offered"
    failureeffect = "No communication between process will happen, thus no information can be exchanged, thus any overall system functionality can stop."
    version = 1
    safety = ScoreReq.Asil.B
    rationale = "We added an AoU that no Safety-goal shall be harmed, if a service is not offered. Thus, this failure cannot have any safety-related bad effect."
}
